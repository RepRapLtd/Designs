# -*- coding: utf-8 -*-

# Macro Begin: /home/isaacmoyse/Desktop/rrlcloud/RepRapLtd/Engineering/Isaac/test6.FCMacro +++++++++++++++++++++++++++++++++++++++++++++++++
import FreeCAD
import Part

#def cut():
	#App.activeDocument().Cut.Base = a
	#App.activeDocument().Cut.Tool = b


App.ActiveDocument.addObject("Part::Box","Box")
App.ActiveDocument.ActiveObject.Label = "Cube"
App.ActiveDocument.recompute()
App.ActiveDocument.addObject("Part::Cylinder","Cylinder")
App.ActiveDocument.ActiveObject.Label = "Cylinder"
App.ActiveDocument.recompute()
#Gui.SendMsgToActiveView("ViewFit")
App.activeDocument().addObject("Part::Cut","Cut")
a=App.activeDocument().Box
b=App.activeDocument().Cylinder
App.activeDocument().Cut.Base = a
App.activeDocument().Cut.Tool = b
#Gui.activeDocument().Box.Visibility=False
#Gui.activeDocument().Cylinder.Visibility=False
#Gui.ActiveDocument.Cut.ShapeColor=Gui.ActiveDocument.Box.ShapeColor
#Gui.ActiveDocument.Cut.DisplayMode=Gui.ActiveDocument.Box.DisplayMode
App.ActiveDocument.recompute()
# Macro End: /home/isaacmoyse/Desktop/rrlcloud/RepRapLtd/Engineering/Isaac/test6.FCMacro +++++++++++++++++++++++++++++++++++++++++++++++++
