# -*- coding: utf-8 -*-

# Macro Begin: /home/isaacmoyse/Desktop/rrlcloud/RepRapLtd/Engineering/Isaac/1233333333333.FCMacro +++++++++++++++++++++++++++++++++++++++++++++++++
import FreeCAD
import Part

App.ActiveDocument.addObject("Part::Cylinder","Cylinder")
App.ActiveDocument.ActiveObject.Label = "Cylinder"
App.ActiveDocument.recompute()
#Gui.SendMsgToActiveView("ViewFit")
#Gui.activeDocument().activeView().viewFront()
#Gui.activeDocument().activeView().viewTop()
FreeCAD.getDocument("Unnamed").getObject("Cylinder").Height = '11 mm'
FreeCAD.getDocument("Unnamed").getObject("Cylinder").Height = '12 mm'
FreeCAD.getDocument("Unnamed").getObject("Cylinder").Height = '13 mm'
FreeCAD.getDocument("Unnamed").getObject("Cylinder").Height = '14 mm'
FreeCAD.getDocument("Unnamed").getObject("Cylinder").Height = '15 mm'
FreeCAD.getDocument("Unnamed").getObject("Cylinder").Height = '16 mm'
FreeCAD.getDocument("Unnamed").getObject("Cylinder").Height = '17 mm'
FreeCAD.getDocument("Unnamed").getObject("Cylinder").Height = '18 mm'
FreeCAD.getDocument("Unnamed").getObject("Cylinder").Height = '17 mm'
FreeCAD.getDocument("Unnamed").getObject("Cylinder").Height = '16 mm'
FreeCAD.getDocument("Unnamed").getObject("Cylinder").Height = '15 mm'
FreeCAD.getDocument("Unnamed").getObject("Cylinder").Height = '14 mm'
FreeCAD.getDocument("Unnamed").getObject("Cylinder").Height = '13 mm'
FreeCAD.getDocument("Unnamed").getObject("Cylinder").Height = '12 mm'
FreeCAD.getDocument("Unnamed").getObject("Cylinder").Height = '11 mm'
FreeCAD.getDocument("Unnamed").getObject("Cylinder").Height = '10 mm'
FreeCAD.getDocument("Unnamed").getObject("Cylinder").Height = '11 mm'
FreeCAD.getDocument("Unnamed").getObject("Cylinder").Height = '12 mm'
FreeCAD.getDocument("Unnamed").getObject("Cylinder").Height = '13 mm'
FreeCAD.getDocument("Unnamed").getObject("Cylinder").Height = '14 mm'
FreeCAD.getDocument("Unnamed").getObject("Cylinder").Height = '15 mm'
FreeCAD.getDocument("Unnamed").getObject("Cylinder").Height = '16 mm'
FreeCAD.getDocument("Unnamed").getObject("Cylinder").Height = '17 mm'
FreeCAD.getDocument("Unnamed").getObject("Cylinder").Height = '18 mm'
FreeCAD.getDocument("Unnamed").getObject("Cylinder").Height = '19 mm'
FreeCAD.getDocument("Unnamed").getObject("Cylinder").Height = '20 mm'
FreeCAD.getDocument("Unnamed").getObject("Cylinder").Height = '21 mm'
FreeCAD.getDocument("Unnamed").getObject("Cylinder").Height = '22 mm'
FreeCAD.getDocument("Unnamed").getObject("Cylinder").Height = '23 mm'
FreeCAD.getDocument("Unnamed").getObject("Cylinder").Height = '24 mm'
FreeCAD.getDocument("Unnamed").getObject("Cylinder").Height = '25 mm'
FreeCAD.getDocument("Unnamed").getObject("Cylinder").Height = '26 mm'
FreeCAD.getDocument("Unnamed").getObject("Cylinder").Height = '27 mm'
FreeCAD.getDocument("Unnamed").getObject("Cylinder").Height = '28 mm'
FreeCAD.getDocument("Unnamed").getObject("Cylinder").Radius = '3 mm'
FreeCAD.getDocument("Unnamed").getObject("Cylinder").Radius = '4 mm'
FreeCAD.getDocument("Unnamed").getObject("Cylinder").Radius = '5 mm'
FreeCAD.getDocument("Unnamed").getObject("Cylinder").Radius = '6 mm'
FreeCAD.getDocument("Unnamed").getObject("Cylinder").Radius = '5 mm'
FreeCAD.getDocument("Unnamed").getObject("Cylinder").Radius = '6 mm'
FreeCAD.getDocument("Unnamed").getObject("Cylinder").Radius = '7 mm'
FreeCAD.getDocument("Unnamed").getObject("Cylinder").Radius = '8 mm'
FreeCAD.getDocument("Unnamed").getObject("Cylinder").Radius = '9 mm'
FreeCAD.getDocument("Unnamed").getObject("Cylinder").Radius = '8 mm'
FreeCAD.getDocument("Unnamed").getObject("Cylinder").Radius = '9 mm'
FreeCAD.getDocument("Unnamed").getObject("Cylinder").Radius = '10 mm'
FreeCAD.getDocument("Unnamed").getObject("Cylinder").Radius = '11 mm'
FreeCAD.getDocument("Unnamed").getObject("Cylinder").Radius = '12 mm'
FreeCAD.getDocument("Unnamed").getObject("Cylinder").Radius = '13 mm'
FreeCAD.getDocument("Unnamed").getObject("Cylinder").Radius = '14 mm'
FreeCAD.getDocument("Unnamed").getObject("Cylinder").Radius = '15 mm'
FreeCAD.getDocument("Unnamed").getObject("Cylinder").Radius = '16 mm'
FreeCAD.getDocument("Unnamed").getObject("Cylinder").Radius = '17 mm'
FreeCAD.getDocument("Unnamed").getObject("Cylinder").Radius = '18 mm'
FreeCAD.getDocument("Unnamed").getObject("Cylinder").Radius = '19 mm'
FreeCAD.getDocument("Unnamed").getObject("Cylinder").Radius = '20 mm'
FreeCAD.getDocument("Unnamed").getObject("Cylinder").Radius = '21 mm'
FreeCAD.getDocument("Unnamed").getObject("Cylinder").Radius = '22 mm'
FreeCAD.getDocument("Unnamed").getObject("Cylinder").Radius = '21 mm'
FreeCAD.getDocument("Unnamed").getObject("Cylinder").Radius = '20 mm'
FreeCAD.getDocument("Unnamed").getObject("Cylinder").Radius = '19 mm'
FreeCAD.getDocument("Unnamed").getObject("Cylinder").Radius = '18 mm'
FreeCAD.getDocument("Unnamed").getObject("Cylinder").Radius = '17 mm'
FreeCAD.getDocument("Unnamed").getObject("Cylinder").Radius = '16 mm'
FreeCAD.getDocument("Unnamed").getObject("Cylinder").Angle = 359.00
FreeCAD.getDocument("Unnamed").getObject("Cylinder").Angle = 358.00
FreeCAD.getDocument("Unnamed").getObject("Cylinder").Angle = 357.00
FreeCAD.getDocument("Unnamed").getObject("Cylinder").Angle = 356.00
FreeCAD.getDocument("Unnamed").getObject("Cylinder").Angle = 355.00
FreeCAD.getDocument("Unnamed").getObject("Cylinder").Angle = 354.00
FreeCAD.getDocument("Unnamed").getObject("Cylinder").Angle = 353.00
FreeCAD.getDocument("Unnamed").getObject("Cylinder").Angle = 352.00
FreeCAD.getDocument("Unnamed").getObject("Cylinder").Angle = 353.00
FreeCAD.getDocument("Unnamed").getObject("Cylinder").Angle = 352.00
FreeCAD.getDocument("Unnamed").getObject("Cylinder").Angle = 351.00
FreeCAD.getDocument("Unnamed").getObject("Cylinder").Angle = 350.00
FreeCAD.getDocument("Unnamed").getObject("Cylinder").Angle = 349.00
FreeCAD.getDocument("Unnamed").getObject("Cylinder").Angle = 348.00
FreeCAD.getDocument("Unnamed").getObject("Cylinder").Angle = 347.00
FreeCAD.getDocument("Unnamed").getObject("Cylinder").Angle = 346.00
FreeCAD.getDocument("Unnamed").getObject("Cylinder").Angle = 345.00
FreeCAD.getDocument("Unnamed").getObject("Cylinder").Angle = 344.00
FreeCAD.getDocument("Unnamed").getObject("Cylinder").Angle = 343.00
FreeCAD.getDocument("Unnamed").getObject("Cylinder").Angle = 342.00
FreeCAD.getDocument("Unnamed").getObject("Cylinder").Angle = 341.00
FreeCAD.getDocument("Unnamed").getObject("Cylinder").Angle = 340.00
FreeCAD.getDocument("Unnamed").getObject("Cylinder").Angle = 339.00
FreeCAD.getDocument("Unnamed").getObject("Cylinder").Angle = 338.00
FreeCAD.getDocument("Unnamed").getObject("Cylinder").Angle = 337.00
FreeCAD.getDocument("Unnamed").getObject("Cylinder").Angle = 336.00
FreeCAD.getDocument("Unnamed").getObject("Cylinder").Angle = 335.00
FreeCAD.getDocument("Unnamed").getObject("Cylinder").Angle = 334.00
FreeCAD.getDocument("Unnamed").getObject("Cylinder").Angle = 333.00
FreeCAD.getDocument("Unnamed").getObject("Cylinder").Angle = 332.00
FreeCAD.getDocument("Unnamed").getObject("Cylinder").Angle = 331.00
FreeCAD.getDocument("Unnamed").getObject("Cylinder").Angle = 330.00
FreeCAD.getDocument("Unnamed").getObject("Cylinder").Angle = 329.00
FreeCAD.getDocument("Unnamed").getObject("Cylinder").Angle = 328.00
FreeCAD.getDocument("Unnamed").getObject("Cylinder").Angle = 327.00
FreeCAD.getDocument("Unnamed").getObject("Cylinder").Angle = 326.00
FreeCAD.getDocument("Unnamed").getObject("Cylinder").Angle = 325.00
FreeCAD.getDocument("Unnamed").getObject("Cylinder").Angle = 324.00
FreeCAD.getDocument("Unnamed").getObject("Cylinder").Angle = 323.00
FreeCAD.getDocument("Unnamed").getObject("Cylinder").Angle = 322.00
FreeCAD.getDocument("Unnamed").getObject("Cylinder").Angle = 321.00
FreeCAD.getDocument("Unnamed").getObject("Cylinder").Angle = 320.00
FreeCAD.getDocument("Unnamed").getObject("Cylinder").Angle = 319.00
FreeCAD.getDocument("Unnamed").getObject("Cylinder").Angle = 318.00
FreeCAD.getDocument("Unnamed").getObject("Cylinder").Angle = 317.00
FreeCAD.getDocument("Unnamed").getObject("Cylinder").Angle = 316.00
FreeCAD.getDocument("Unnamed").getObject("Cylinder").Angle = 315.00
FreeCAD.getDocument("Unnamed").getObject("Cylinder").Angle = 314.00
FreeCAD.getDocument("Unnamed").getObject("Cylinder").Angle = 313.00
FreeCAD.getDocument("Unnamed").getObject("Cylinder").Angle = 312.00
FreeCAD.getDocument("Unnamed").getObject("Cylinder").Angle = 311.00
FreeCAD.getDocument("Unnamed").getObject("Cylinder").Angle = 310.00
FreeCAD.getDocument("Unnamed").getObject("Cylinder").Angle = 309.00
FreeCAD.getDocument("Unnamed").getObject("Cylinder").Angle = 310.00
FreeCAD.getDocument("Unnamed").getObject("Cylinder").Angle = 311.00
FreeCAD.getDocument("Unnamed").getObject("Cylinder").Angle = 312.00
FreeCAD.getDocument("Unnamed").getObject("Cylinder").Angle = 313.00
FreeCAD.getDocument("Unnamed").getObject("Cylinder").Angle = 314.00
FreeCAD.getDocument("Unnamed").getObject("Cylinder").Angle = 315.00
FreeCAD.getDocument("Unnamed").getObject("Cylinder").Angle = 316.00
FreeCAD.getDocument("Unnamed").getObject("Cylinder").Angle = 317.00
FreeCAD.getDocument("Unnamed").getObject("Cylinder").Angle = 318.00
FreeCAD.getDocument("Unnamed").getObject("Cylinder").Angle = 319.00
FreeCAD.getDocument("Unnamed").getObject("Cylinder").Angle = 320.00
FreeCAD.getDocument("Unnamed").getObject("Cylinder").Angle = 321.00
FreeCAD.getDocument("Unnamed").getObject("Cylinder").Angle = 322.00
FreeCAD.getDocument("Unnamed").getObject("Cylinder").Angle = 323.00
FreeCAD.getDocument("Unnamed").getObject("Cylinder").Angle = 324.00
FreeCAD.getDocument("Unnamed").getObject("Cylinder").Angle = 325.00
FreeCAD.getDocument("Unnamed").getObject("Cylinder").Angle = 326.00
FreeCAD.getDocument("Unnamed").getObject("Cylinder").Angle = 327.00
FreeCAD.getDocument("Unnamed").getObject("Cylinder").Angle = 328.00
FreeCAD.getDocument("Unnamed").getObject("Cylinder").Angle = 329.00
FreeCAD.getDocument("Unnamed").getObject("Cylinder").Angle = 330.00
FreeCAD.getDocument("Unnamed").getObject("Cylinder").Angle = 331.00
FreeCAD.getDocument("Unnamed").getObject("Cylinder").Angle = 332.00
FreeCAD.getDocument("Unnamed").getObject("Cylinder").Angle = 333.00
FreeCAD.getDocument("Unnamed").getObject("Cylinder").Angle = 334.00
FreeCAD.getDocument("Unnamed").getObject("Cylinder").Angle = 335.00
FreeCAD.getDocument("Unnamed").getObject("Cylinder").Angle = 336.00
FreeCAD.getDocument("Unnamed").getObject("Cylinder").Angle = 337.00
FreeCAD.getDocument("Unnamed").getObject("Cylinder").Angle = 338.00
FreeCAD.getDocument("Unnamed").getObject("Cylinder").Angle = 339.00
FreeCAD.getDocument("Unnamed").getObject("Cylinder").Angle = 340.00
FreeCAD.getDocument("Unnamed").getObject("Cylinder").Angle = 341.00
FreeCAD.getDocument("Unnamed").getObject("Cylinder").Angle = 342.00
FreeCAD.getDocument("Unnamed").getObject("Cylinder").Angle = 343.00
FreeCAD.getDocument("Unnamed").getObject("Cylinder").Angle = 344.00
FreeCAD.getDocument("Unnamed").getObject("Cylinder").Angle = 345.00
FreeCAD.getDocument("Unnamed").getObject("Cylinder").Angle = 346.00
FreeCAD.getDocument("Unnamed").getObject("Cylinder").Angle = 347.00
FreeCAD.getDocument("Unnamed").getObject("Cylinder").Angle = 348.00
FreeCAD.getDocument("Unnamed").getObject("Cylinder").Angle = 349.00
FreeCAD.getDocument("Unnamed").getObject("Cylinder").Angle = 350.00
FreeCAD.getDocument("Unnamed").getObject("Cylinder").Angle = 351.00
FreeCAD.getDocument("Unnamed").getObject("Cylinder").Angle = 352.00
FreeCAD.getDocument("Unnamed").getObject("Cylinder").Angle = 353.00
FreeCAD.getDocument("Unnamed").getObject("Cylinder").Angle = 354.00
FreeCAD.getDocument("Unnamed").getObject("Cylinder").Angle = 355.00
FreeCAD.getDocument("Unnamed").getObject("Cylinder").Angle = 356.00
FreeCAD.getDocument("Unnamed").getObject("Cylinder").Angle = 357.00
FreeCAD.getDocument("Unnamed").getObject("Cylinder").Angle = 358.00
FreeCAD.getDocument("Unnamed").getObject("Cylinder").Angle = 359.00
FreeCAD.getDocument("Unnamed").getObject("Cylinder").Angle = 360.00
FreeCAD.getDocument("Unnamed").getObject("Cylinder").Angle = 359.00
FreeCAD.getDocument("Unnamed").getObject("Cylinder").Angle = 360.00
FreeCAD.getDocument("Unnamed").getObject("Cylinder").Height = '29 mm'
FreeCAD.getDocument("Unnamed").getObject("Cylinder").Height = '30 mm'
FreeCAD.getDocument("Unnamed").getObject("Cylinder").Height = '31 mm'
FreeCAD.getDocument("Unnamed").getObject("Cylinder").Height = '32 mm'
FreeCAD.getDocument("Unnamed").getObject("Cylinder").Height = '33 mm'
FreeCAD.getDocument("Unnamed").getObject("Cylinder").Height = '34 mm'
FreeCAD.getDocument("Unnamed").getObject("Cylinder").Height = '35 mm'
FreeCAD.getDocument("Unnamed").getObject("Cylinder").Height = '36 mm'
FreeCAD.getDocument("Unnamed").getObject("Cylinder").Height = '37 mm'
FreeCAD.getDocument("Unnamed").getObject("Cylinder").Height = '38 mm'
FreeCAD.getDocument("Unnamed").getObject("Cylinder").Height = '37 mm'
FreeCAD.getDocument("Unnamed").getObject("Cylinder").Radius = '15 mm'
FreeCAD.getDocument("Unnamed").getObject("Cylinder").Radius = '14 mm'
FreeCAD.getDocument("Unnamed").getObject("Cylinder").Radius = '13 mm'
FreeCAD.getDocument("Unnamed").getObject("Cylinder").Radius = '12 mm'
FreeCAD.getDocument("Unnamed").getObject("Cylinder").Radius = '11 mm'
FreeCAD.getDocument("Unnamed").getObject("Cylinder").Radius = '10 mm'
FreeCAD.getDocument("Unnamed").getObject("Cylinder").Radius = '9 mm'
FreeCAD.getDocument("Unnamed").getObject("Cylinder").Radius = '8 mm'
FreeCAD.getDocument("Unnamed").getObject("Cylinder").Radius = '7 mm'
FreeCAD.getDocument("Unnamed").getObject("Cylinder").Radius = '6 mm'
FreeCAD.getDocument("Unnamed").getObject("Cylinder").Radius = '5 mm'
FreeCAD.getDocument("Unnamed").getObject("Cylinder").Radius = '4 mm'
FreeCAD.getDocument("Unnamed").getObject("Cylinder").Radius = '3 mm'
FreeCAD.getDocument("Unnamed").getObject("Cylinder").Radius = '2 mm'
FreeCAD.getDocument("Unnamed").getObject("Cylinder").Radius = '1 mm'
FreeCAD.getDocument("Unnamed").getObject("Cylinder").Radius = '0 mm'
FreeCAD.getDocument("Unnamed").getObject("Cylinder").Radius = '1 mm'
FreeCAD.getDocument("Unnamed").getObject("Cylinder").Radius = '2 mm'
FreeCAD.getDocument("Unnamed").getObject("Cylinder").Radius = '3 mm'
FreeCAD.getDocument("Unnamed").getObject("Cylinder").Radius = '4 mm'
FreeCAD.getDocument("Unnamed").getObject("Cylinder").Radius = '5 mm'
FreeCAD.getDocument("Unnamed").getObject("Cylinder").Radius = '6 mm'
FreeCAD.getDocument("Unnamed").getObject("Cylinder").Radius = '7 mm'
FreeCAD.getDocument("Unnamed").getObject("Cylinder").Radius = '8 mm'
FreeCAD.getDocument("Unnamed").getObject("Cylinder").Radius = '9 mm'
FreeCAD.getDocument("Unnamed").getObject("Cylinder").Radius = '10 mm'
FreeCAD.getDocument("Unnamed").getObject("Cylinder").Radius = '11 mm'
FreeCAD.getDocument("Unnamed").getObject("Cylinder").Radius = '12 mm'
FreeCAD.getDocument("Unnamed").getObject("Cylinder").Radius = '13 mm'
FreeCAD.getDocument("Unnamed").getObject("Cylinder").Radius = '14 mm'
FreeCAD.getDocument("Unnamed").getObject("Cylinder").Radius = '15 mm'
FreeCAD.getDocument("Unnamed").getObject("Cylinder").Radius = '16 mm'
FreeCAD.getDocument("Unnamed").getObject("Cylinder").Radius = '17 mm'
FreeCAD.getDocument("Unnamed").getObject("Cylinder").Radius = '18 mm'
FreeCAD.getDocument("Unnamed").getObject("Cylinder").Radius = '19 mm'
FreeCAD.getDocument("Unnamed").getObject("Cylinder").Radius = '20 mm'
FreeCAD.getDocument("Unnamed").getObject("Cylinder").Radius = '21 mm'
FreeCAD.getDocument("Unnamed").getObject("Cylinder").Radius = '22 mm'
FreeCAD.getDocument("Unnamed").getObject("Cylinder").Radius = '23 mm'
# Macro End: /home/isaacmoyse/Desktop/rrlcloud/RepRapLtd/Engineering/Isaac/1233333333333.FCMacro +++++++++++++++++++++++++++++++++++++++++++++++++
